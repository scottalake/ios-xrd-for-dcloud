-- *****************************************************************
-- CISCO-PROCESS-MIB.my: MIB for CPU and process statistics
--
-- August 1998, Ramanathan R. Kavasseri
--
-- Copyright (c) 1998, 2001, 2018, 2021 by cisco Systems, Inc.
-- All rights reserved.
-- *****************************************************************
--
-- This mib was extracted from RFC xxxx

CISCO-PROCESS-MIB DEFINITIONS ::= BEGIN

IMPORTS
	MODULE-IDENTITY,
	OBJECT-TYPE,
	Counter32,
	Gauge32, Unsigned32
		FROM SNMPv2-SMI
	TimeStamp, 
	DisplayString
		FROM SNMPv2-TC
	MODULE-COMPLIANCE,
	OBJECT-GROUP
		FROM SNMPv2-CONF
	ciscoMgmt
		FROM CISCO-SMI
	EntPhysicalIndexOrZero
		FROM CISCO-TC;


ciscoProcessMIB MODULE-IDENTITY
	LAST-UPDATED	"200105180000Z"
	ORGANIZATION	"Cisco Systems, Inc."
        CONTACT-INFO
                "       Cisco Systems
                        Customer Service
 
                Postal: 170 W Tasman Drive
                        San Jose, CA  95134
                        USA
 
                   Tel: +1 800 553-NETS
 
                E-mail: cs-snmp@cisco.com"
	DESCRIPTION
		"The MIB module to describe active system processes."
	REVISION	"200105180000Z"
	DESCRIPTION
		"The objects cpmProcExtUtil5Sec, cpmProcExtUtil1Min, 
		cpmProcExtUtil5Min,cpmCPUTotal5sec, cpmCPUTotal1min 
		and cpmCPUTotal5min are deprecated to increase the
		value range as 0..100. The table cpmProcessExtTable
		is deprecated. The new objects added are 
		cpmProcessExtRevTable, cpmProcExtMemAllocatedRev,
		cpmProcExtMemFreedRev, cpmProcExtInvokedRev, 
		cpmProcExtRuntimeRev, cpmProcExtUtil5SecRev,
		cpmProcExtUtil1MinRev, cpmCPUTotal5MinRev, 
		cpmCPUTotal5secRev, cpmCPUTotal1minRev and 
		cpmCPUTotal5minRev."
	REVISION        "9804150000Z"
	DESCRIPTION
		"Initial version of this MIB."		
	::= { ciscoMgmt 109 }

-- This MIB displays memory and CPU utilization on cisco devices. CPU 
-- utilization will give a general idea of how busy the processor is. 
-- The numbers are a ratio of the current idle time over the longest 
-- idle time. Please note that this information should be used as an 
-- estimate only. 

ciscoProcessMIBObjects	OBJECT IDENTIFIER ::= { ciscoProcessMIB 1 }
cpmCPU		OBJECT IDENTIFIER ::= { ciscoProcessMIBObjects 1 }
cpmProcess		OBJECT IDENTIFIER ::= { ciscoProcessMIBObjects 2 }


--Cisco CPU Total Table

cpmCPUTotalTable OBJECT-TYPE
	SYNTAX		SEQUENCE OF CpmCPUTotalEntry
	MAX-ACCESS      not-accessible
        STATUS          current
        DESCRIPTION
		"A table of overall CPU statistics. "
	::= { cpmCPU 1 }

cpmCPUTotalEntry OBJECT-TYPE
	SYNTAX		CpmCPUTotalEntry
	MAX-ACCESS      not-accessible
        STATUS          current
        DESCRIPTION
		"Overall information about the CPU load. Entries in this
		table come and go as CPUs are added and removed from the
		system."
	INDEX	{ cpmCPUTotalIndex }
	::= { cpmCPUTotalTable 1 }

CpmCPUTotalEntry ::=
	SEQUENCE {
		cpmCPUTotalIndex		Unsigned32,
		cpmCPUTotalPhysicalIndex	EntPhysicalIndexOrZero,
		--cpmCPUTotal5sec		Gauge32,  deprecated
		--cpmCPUTotal1min		Gauge32,  deprecated
		--cpmCPUTotal5min		Gauge32,  deprecated
		--cpmCPUTotal15min		Gauge32,  deprecated
		--cpmCPUTotal5secRev		Gauge32,  deprecated
		cpmCPUTotal1minRev		Gauge32,
		cpmCPUTotal5minRev		Gauge32,
		cpmCPUTotal15minRev		Gauge32
	}

cpmCPUTotalIndex OBJECT-TYPE
	SYNTAX          Unsigned32 (1.. 4294967295)
	MAX-ACCESS      not-accessible
	STATUS          current
	DESCRIPTION
		"An index that uniquely represents a CPU (or group of CPUs)
		whose CPU load information is reported by a row in this table.
		This index is assigned arbitrarily by the engine
		and is not saved over reboots."
	::= { cpmCPUTotalEntry 1 }

cpmCPUTotalPhysicalIndex OBJECT-TYPE
	SYNTAX	        EntPhysicalIndexOrZero
        MAX-ACCESS      read-only
        STATUS          current
        DESCRIPTION
		"The entPhysicalIndex of the physical entity for which
		 the CPU statistics in this entry are maintained.
		 The physical entity can be a CPU chip, a group of CPUs,
		 a CPU card etc. The exact type of this entity is described by
		 its entPhysicalVendorType value. If the CPU statistics
		 in this entry correspond to more than one physical entity
		 (or to no physical entity), or if the entPhysicalTable is
		 not supported on the SNMP agent, the value of this object
		 must be zero."
	::= { cpmCPUTotalEntry 2 }

--CSCvw30835 Deprecated OIDs needs to be removed from the show snmp mib object-name
--cpmCPUTotal5sec OBJECT-TYPE
--        SYNTAX          Gauge32 (1..100)
--        MAX-ACCESS      read-only
--        STATUS          deprecated
--        DESCRIPTION
--		"The overall CPU busy percentage in the last 5 second 
--		period. This object obsoletes the busyPer object from 
--		the OLD-CISCO-SYSTEM-MIB. This object is deprecated
--		by cpmCPUTotal5secRev which has the changed range of
--		value (0..100)."
--	::= { cpmCPUTotalEntry 3 }

--CSCvw30835 Deprecated OIDs needs to be removed from the show snmp mib object-name
--cpmCPUTotal1min OBJECT-TYPE
--        SYNTAX          Gauge32  (1..100)
--        MAX-ACCESS      read-only
--        STATUS          deprecated
--        DESCRIPTION
--		"The overall CPU busy percentage in the last 1 minute
--		period. This object obsoletes the avgBusy1 object from 
--		the OLD-CISCO-SYSTEM-MIB. This object is deprecated
--		by cpmCPUTotal1minRev which has the changed range
--		of value (0..100)."
--	::= { cpmCPUTotalEntry 4 }

--CSCvw30835 Deprecated OIDs needs to be removed from the show snmp mib object-name
--cpmCPUTotal5min OBJECT-TYPE
--        SYNTAX          Gauge32 (1..100)
--        MAX-ACCESS      read-only
--        STATUS          deprecated
--        DESCRIPTION
--		"The overall CPU busy percentage in the last 5 minute
--		period. This object deprecates the avgBusy5 object from 
--		the OLD-CISCO-SYSTEM-MIB. This object is deprecated
--		by cpmCPUTotal5minRev which has the changed range 
--		of value (0..100)."
--	::= { cpmCPUTotalEntry 5 }

--CSCvw30835 Deprecated OIDs needs to be removed from the show snmp mib object-name
--cpmCPUTotal15min OBJECT-TYPE
--        SYNTAX          Gauge32 (1..100)
--        MAX-ACCESS      read-only
--        STATUS          deprecated
--        DESCRIPTION
--		"The overall CPU busy percentage in the last 15 minute
--		period. This object deprecates the avgBusy5 object from 
--		the OLD-CISCO-SYSTEM-MIB. This object is deprecated
--		by cpmCPUTotal15minRev which has the changed range 
--		of value (0..100)."
--	::= { cpmCPUTotalEntry 30 }

--CSCvw30835 Deprecated OIDs needs to be removed from the show snmp mib object-name
--cpmCPUTotal5secRev OBJECT-TYPE
--        SYNTAX          Gauge32 (0..100)
--	UNITS		"percent"
--        MAX-ACCESS      read-only
--        STATUS          current
--        DESCRIPTION
--		"The overall CPU busy percentage in the last 5 second 
--		period. This object deprecates the object cpmCPUTotal5sec 
--		and increases the value range to (0..100)."
--	::= { cpmCPUTotalEntry 6 }

cpmCPUTotal1minRev OBJECT-TYPE
        SYNTAX          Gauge32  (0..100)
        UNITS		"percent"
	MAX-ACCESS      read-only
        STATUS          current
        DESCRIPTION
		"The overall CPU busy percentage in the last 1 minute
		period. This object deprecates the object cpmCPUTotal1min 
		and increases the value range to (0..100)."
	::= { cpmCPUTotalEntry 7 }

cpmCPUTotal5minRev OBJECT-TYPE
        SYNTAX          Gauge32 (0..100)
	UNITS		"percent"
        MAX-ACCESS      read-only
        STATUS          current
        DESCRIPTION
		"The overall CPU busy percentage in the last 5 minute
		period. This object deprecates the object cpmCPUTotal5min 
		and increases the value range to (0..100)."
	::= { cpmCPUTotalEntry 8 }

cpmCPUTotal15minRev OBJECT-TYPE
        SYNTAX          Gauge32 (0..100)
	UNITS		"percent"
        MAX-ACCESS      read-only
        STATUS          current
        DESCRIPTION
		"The overall CPU busy percentage in the last 15 minute
		period. This object deprecates the object cpmCPUTotal15min 
		and increases the value range to (0..100)."
	::= { cpmCPUTotalEntry 31 }

-- Cisco Processes Common Table

cpmProcessTable OBJECT-TYPE
	SYNTAX		SEQUENCE OF CpmProcessEntry
        MAX-ACCESS      not-accessible
        STATUS          current
        DESCRIPTION
		"A table of generic information on all active 
		processes on this device."
	::= { cpmProcess 1 }

cpmProcessEntry OBJECT-TYPE
	SYNTAX    	CpmProcessEntry
        MAX-ACCESS      not-accessible
        STATUS          current
        DESCRIPTION
		"Generic information about an active process on this 
		device. Entries in this table come and go as processes are 
		created and destroyed by the device."
	INDEX	{ cpmCPUTotalIndex, cpmProcessPID }
	::= { cpmProcessTable 1 }

CpmProcessEntry ::=
	SEQUENCE {
		cpmProcessPID
			Unsigned32,
		cpmProcessName 
			DisplayString,
		--cpmProcessuSecs
		--	Unsigned32,  deprecated
		cpmProcessAverageUSecs
			Unsigned32,
		cpmProcessTimeCreated
			TimeStamp
	}

cpmProcessPID OBJECT-TYPE
	SYNTAX    	Unsigned32
        MAX-ACCESS      read-only
        STATUS          current
        DESCRIPTION
		"This object contains the process ID. cpmTimeCreated
		should be checked against the last time it was polled,
		and if it has changed the PID has been reused and the
		 entire entry should be polled again."
	::= { cpmProcessEntry 1 }

cpmProcessName OBJECT-TYPE
	SYNTAX    	DisplayString(SIZE(1..32))
        MAX-ACCESS      read-only
        STATUS          current
        DESCRIPTION
		"The name associated with this process. If the name is
		longer than 32 characters, it will be truncated to the first
		31 characters, and a `*' will be appended as the last
		character to imply this is a truncated process name."
	::= { cpmProcessEntry 2 }

--CSCvw30835 Deprecated OIDs needs to be removed from the show snmp mib object-name
--cpmProcessuSecs OBJECT-TYPE
--        SYNTAX          Unsigned32
--        UNITS           "microseconds"
--        MAX-ACCESS      read-only
--        STATUS          deprecated
--        DESCRIPTION
--                "Average elapsed CPU time in microseconds when the 
--                process was active. This object is deprecated
--		by cpmProcessAverageUSecs."
--       ::= { cpmProcessEntry 4 }

cpmProcessTimeCreated OBJECT-TYPE
	SYNTAX		TimeStamp
	MAX-ACCESS      read-only
        STATUS          current
        DESCRIPTION
		"The time when the process was created. The process ID 
		and the time when the process was created, uniquely 
		identifies a process."
	::= { cpmProcessEntry 5 }

cpmProcessAverageUSecs OBJECT-TYPE
	SYNTAX		Unsigned32
	UNITS		"microseconds"
	MAX-ACCESS      read-only
        STATUS          current
        DESCRIPTION
		"Average elapsed CPU time in microseconds when the 
		process was active. This object deprecates the
		object cpmProcessuSecs."
	::= { cpmProcessEntry 6 }


-- Cisco processes detail Table.  This table is mandatory on systems 
-- that have the internal capability to keep the information.

--CSCvw30835 Deprecated OIDs needs to be removed from the show snmp mib object-name
--cpmProcessExtTable OBJECT-TYPE
--	SYNTAX     	SEQUENCE OF CpmProcessExtEntry
--        MAX-ACCESS      not-accessible
--        STATUS          deprecated
--        DESCRIPTION
--		"This table contains information that may or may
--		not be available on all cisco devices. It contains
--		additional objects for the more general
--		cpmProcessTable. This object is deprecated by
--		cpmProcessExtRevTable."
--	::= { cpmProcess 2 }

--CSCvw30835 Deprecated OIDs needs to be removed from the show snmp mib object-name
--cpmProcessExtEntry OBJECT-TYPE
--	SYNTAX		CpmProcessExtEntry
--	MAX-ACCESS  	not-accessible
--	STATUS		deprecated
--	DESCRIPTION
--		"An entry containing additional information for
--		a particular process. This object is deprecated by
--		cpmProcessExtRevEntry."
--	AUGMENTS        { cpmProcessEntry }
--	::= { cpmProcessExtTable 1 } 

--CSCvw30835 Deprecated OIDs needs to be removed from the show snmp mib object-name
--CpmProcessExtEntry ::=
--	SEQUENCE {
		--cpmProcExtMemAllocated
		--	Gauge32,
		--cpmProcExtMemFreed
		--	Gauge32,
		--cpmProcExtInvoked
		--	Counter32,
		--cpmProcExtRuntime
		--	Counter32
		--cpmProcExtUtil5Sec
		--	Gauge32,	
		--cpmProcExtUtil1Min
		--	Gauge32,	
		--cpmProcExtUtil5Min
		--	Gauge32,	
		--cpmProcExtPriority
		--	INTEGER		
--	}

--CSCvw30835 Deprecated OIDs needs to be removed from the show snmp mib object-name
--cpmProcExtMemAllocated OBJECT-TYPE
--	SYNTAX    	Gauge32
-- 	UNITS		"bytes"
--        MAX-ACCESS      read-only
--        STATUS          deprecated
--        DESCRIPTION
--		"The sum of all the dynamically allocated memory that
--		this process has received from the system. This includes
--		memory that may have been returned. The sum of freed
--		memory is provided by cpmProcExtMemFreed. This object
--		is deprecated by cpmProcExtMemAllocatedRev."
--	::= { cpmProcessExtEntry 1 }

--CSCvw30835 Deprecated OIDs needs to be removed from the show snmp mib object-name
--cpmProcExtMemFreed OBJECT-TYPE
--	SYNTAX    	Gauge32
--	UNITS		"bytes"
--       MAX-ACCESS      read-only
--        STATUS          deprecated
--        DESCRIPTION
-- 		"The sum of all memory that this process has returned 
--		to the system. This object is deprecated by 
--		cpmProcExtMemFreedRev."
--	::= { cpmProcessExtEntry 2 }

--CSCvw30835 Deprecated OIDs needs to be removed from the show snmp mib object-name
--cpmProcExtInvoked OBJECT-TYPE
--	SYNTAX    	Counter32
--        MAX-ACCESS      read-only
--        STATUS          deprecated
--        DESCRIPTION
--		"The number of times since cpmTimeCreated that 
--		the process has been invoked. This object is
--		deprecated by cpmProcExtInvokedRev."
--	::= { cpmProcessExtEntry 3 }

--CSCvw30835 Deprecated OIDs needs to be removed from the show snmp mib object-name
--cpmProcExtRuntime OBJECT-TYPE
--	SYNTAX    	Counter32
--	UNITS		"microseconds"
--        MAX-ACCESS      read-only
--        STATUS          deprecated
--        DESCRIPTION
--		"The amount of CPU time the process has used, in 
--		microseconds. This object is deprecated by
--		cpmProcExtRuntimeRev."
--	::= { cpmProcessExtEntry 4 }

--CSCvw30835 Deprecated OIDs needs to be removed from the show snmp mib object-name
--cpmProcExtUtil5Sec OBJECT-TYPE
--        SYNTAX          Gauge32(1..100)
--        MAX-ACCESS      read-only
--        STATUS          deprecated
--        DESCRIPTION
--		"This object provides a general idea of how busy 
--		a process caused the processor to be over a 5 
--		second period. It is determined as a weighted 
--		decaying average of the current idle time over 
--		the longest idle time. Note that this information 
--		should be used as an estimate only. This object is 
--		deprecated by cpmProcExtUtil5SecRev which has the 
--		changed range of value (0..100)."
--	::= { cpmProcessExtEntry 5 }

--CSCvw30835 Deprecated OIDs needs to be removed from the show snmp mib object-name
--cpmProcExtUtil1Min OBJECT-TYPE
--        SYNTAX          Gauge32(1..100)
--        MAX-ACCESS      read-only
--        STATUS          deprecated
--        DESCRIPTION
--		"This object provides a general idea of how busy 
--		a process caused the processor to be over a 1 
--		minute period. It is determined as a weighted 
--		decaying average of the current idle time over the 
--		longest idle time. Note that this information 
--		should be used as an estimate only. This object is 
--		deprecated by cpmProcExtUtil1MinRev which has
--		the changed range of value (0..100)."
--	::= { cpmProcessExtEntry 6 }

--CSCvw30835 Deprecated OIDs needs to be removed from the show snmp mib object-name
--cpmProcExtUtil5Min OBJECT-TYPE
--        SYNTAX          Gauge32(1..100)
--        MAX-ACCESS      read-only
--        STATUS          deprecated
--        DESCRIPTION
--		"This object provides a general idea of how busy 
--		a process caused the processor to be over a 5 
--		minute period. It is determined as a weighted 
--		decaying average of the current idle time over 
--		the longest idle time. Note that this information 
--		should be used as an estimate only. This object
--		is deprecated by cpmProcExtUtil5MinRev which
--		has the changed range of value (0..100)."
--	::= { cpmProcessExtEntry 7 }

--CSCvw30835 Deprecated OIDs needs to be removed from the show snmp mib object-name
--cpmProcExtPriority OBJECT-TYPE
--	SYNTAX		INTEGER {
--				critical(1),
--				high(2),
--				normal(3),
--				low(4),
--				notAssigned(5)
--			}
--	MAX-ACCESS      read-write
--        STATUS          deprecated
--        DESCRIPTION
--		"The priority level at which the process is 
--		running. This object is deprecated by
--		cpmProcExtPriorityRev."
--	::= { cpmProcessExtEntry 8 }

cpmProcessExtRevTable OBJECT-TYPE
	SYNTAX     	SEQUENCE OF CpmProcessExtRevEntry
        MAX-ACCESS      not-accessible
        STATUS          current
        DESCRIPTION
		"This table contains information that may or may
		not be available on all cisco devices. It contains
		additional objects for the more general
		cpmProcessTable. This object deprecates 
		cpmProcessExtTable."
	::= { cpmProcess 3 }

cpmProcessExtRevEntry OBJECT-TYPE
	SYNTAX		CpmProcessExtRevEntry
	MAX-ACCESS  	not-accessible
	STATUS		current
	DESCRIPTION
		"An entry containing additional information for
		a particular process. This object deprecates 
		cpmProcessExtEntry."
	INDEX	{ cpmCPUTotalIndex, cpmProcessPID }
	::= { cpmProcessExtRevTable 1 }

CpmProcessExtRevEntry ::=
	SEQUENCE {
		cpmProcExtMemAllocatedRev
			Gauge32,
		cpmProcExtMemFreedRev
			Gauge32,
		cpmProcExtInvokedRev
			Counter32,
		cpmProcExtRuntimeRev
			Counter32,
		cpmProcExtUtil5SecRev
			Gauge32,	
		cpmProcExtUtil1MinRev
			Gauge32,	
		cpmProcExtUtil5MinRev
			Gauge32,	
		cpmProcExtPriorityRev
			INTEGER,
                cpmProcessTextSegmentSize     
                        Unsigned32,
                cpmProcessDataSegmentSize         
                        Gauge32,
                cpmProcessStackSize               
                        Gauge32,
                cpmProcessDynamicMemorySize       
                        Gauge32		
	}

cpmProcExtMemAllocatedRev OBJECT-TYPE
	SYNTAX    	Gauge32
 	UNITS		"bytes"
        MAX-ACCESS      read-only
        STATUS          current
        DESCRIPTION
		"The sum of all the dynamically allocated memory that
		this process has received from the system. This includes
		memory that may have been returned. The sum of freed
		memory is provided by cpmProcExtMemFreedRev. This object
		deprecates cpmProcExtMemAllocated."
	::= { cpmProcessExtRevEntry 1 }

cpmProcExtMemFreedRev OBJECT-TYPE
	SYNTAX    	Gauge32
	UNITS		"bytes"
        MAX-ACCESS      read-only
        STATUS          current
        DESCRIPTION
 		"The sum of all memory that this process has returned 
		to the system. This object  deprecates 
		cpmProcExtMemFreed."
	::= { cpmProcessExtRevEntry 2 }

cpmProcExtInvokedRev OBJECT-TYPE
	SYNTAX    	Counter32
        MAX-ACCESS      read-only
        STATUS          current
        DESCRIPTION
		"The number of times since cpmTimeCreated that 
		the process has been invoked. This object 
		deprecates cpmProcExtInvoked."
	::= { cpmProcessExtRevEntry 3 }

cpmProcExtRuntimeRev OBJECT-TYPE
	SYNTAX    	Counter32
	UNITS		"microseconds"
        MAX-ACCESS      read-only
        STATUS          current
        DESCRIPTION
		"The amount of CPU time the process has used, in 
		microseconds. This object deprecates
		cpmProcExtRuntime."
	::= { cpmProcessExtRevEntry 4 }

cpmProcExtUtil5SecRev OBJECT-TYPE
        SYNTAX          Gauge32(0..100)
	UNITS		"percent"
        MAX-ACCESS      read-only
        STATUS          current
        DESCRIPTION
		"This object provides a general idea of how busy 
		a process caused the processor to be over a 5 
		second period. It is determined as a weighted 
		decaying average of the current idle time over 
		the longest idle time. Note that this information 
		should be used as an estimate only. This object
		deprecates cpmProcExtUtil5Sec and increases the 
		value range to (0..100)."
	::= { cpmProcessExtRevEntry 5 }

cpmProcExtUtil1MinRev OBJECT-TYPE
        SYNTAX          Gauge32(0..100)
	UNITS		"percent"
        MAX-ACCESS      read-only
        STATUS          current
        DESCRIPTION
		"This object provides a general idea of how busy 
		a process caused the processor to be over a 1 
		minute period. It is determined as a weighted 
		decaying average of the current idle time over the 
		longest idle time. Note that this information 
		should be used as an estimate only. This object 
		deprecates cpmProcExtUtil1Min and increases the value
		range to (0..100)."
	::= { cpmProcessExtRevEntry 6 }

cpmProcExtUtil5MinRev OBJECT-TYPE
        SYNTAX          Gauge32(0..100)
	UNITS		"percent"
	MAX-ACCESS      read-only
        STATUS          current
        DESCRIPTION
		"This object provides a general idea of how busy 
		a process caused the processor to be over a 5 
		minute period. It is determined as a weighted 
		decaying average of the current idle time over 
		the longest idle time. Note that this information 
		should be used as an estimate only. This object
		deprecates cpmProcExtUtil5Min and increases the
		value range to (0..100)."
	::= { cpmProcessExtRevEntry 7 }

cpmProcExtPriorityRev OBJECT-TYPE
	SYNTAX		INTEGER {
				critical(1),
				high(2),
				normal(3),
				low(4),
				notAssigned(5)
			}
	MAX-ACCESS      read-only
        STATUS          current
        DESCRIPTION
		"The priority level at which the process is 
		running. This object deprecates 
		cpmProcExtPriority."
	::= { cpmProcessExtRevEntry 8 }


cpmProcessTextSegmentSize OBJECT-TYPE
        SYNTAX          Unsigned32
        UNITS           "kilo-bytes"
        MAX-ACCESS      read-only
        STATUS          current
        DESCRIPTION
                 "This indicates the text memory of a process and all
                 its shared objects." 
        ::= { cpmProcessExtRevEntry 15 }

cpmProcessDataSegmentSize OBJECT-TYPE
        SYNTAX          Gauge32
        UNITS           "kilo-bytes"
        MAX-ACCESS      read-only
        STATUS          current
        DESCRIPTION
                "This indicates the data segment of a process and
                all its shared objects." 
        ::= { cpmProcessExtRevEntry 16}

cpmProcessStackSize OBJECT-TYPE
        SYNTAX          Gauge32
        UNITS           "kilo-bytes"
        MAX-ACCESS      read-only
        STATUS          current
        DESCRIPTION
                "This indicates the amount of stack memory used by the
                process." 
        ::= { cpmProcessExtRevEntry 17 }

cpmProcessDynamicMemorySize OBJECT-TYPE
        SYNTAX          Gauge32
        UNITS           "kilo-bytes"
        MAX-ACCESS      read-only
        STATUS          current
        DESCRIPTION
                "This indicates the amount of dynamic memory being used
                by the process." 
        ::= { cpmProcessExtRevEntry 18 }

-- notifications

ciscoProcessMIBNotifPrefix OBJECT IDENTIFIER ::= { ciscoProcessMIB 2 }
ciscoProcessMIBNotifs OBJECT IDENTIFIER ::=
	{ ciscoProcessMIBNotifPrefix 0 }

-- (no notifications are currently defined)


-- conformance information

ciscoProcessMIBConformance OBJECT IDENTIFIER ::= { ciscoProcessMIB 3 }
cpmCompliances OBJECT IDENTIFIER ::= { ciscoProcessMIBConformance 1 }
cpmGroups OBJECT IDENTIFIER ::=      { ciscoProcessMIBConformance 2 }

--CSCvw30835 Deprecated OIDs needs to be removed from the show snmp mib object-name
--cProcessMIBCompliance  MODULE-COMPLIANCE
--	STATUS	deprecated
--	DESCRIPTION
--		"The compliance statement for entities which implement
--		the Cisco Process MIB. This is deprecated and new 
--		compliance cProcessMIBComplianceRev is added."
--	MODULE	 this module
--		MANDATORY-GROUPS { cpmCPUTotalGroup, cpmProcessGroup }
--
--
--	GROUP cpmProcessExtGroup
--	DESCRIPTION
--		"The cpmProcessExtGroup is optional for all entities."
--
--	OBJECT		cpmProcExtPriority
--	MIN-ACCESS	read-only
--	DESCRIPTION     "Write access is not required."
--
--	::= { cpmCompliances 1 }

cProcessMIBComplianceRev  MODULE-COMPLIANCE
	STATUS	current
	DESCRIPTION
		"The compliance statement for entities which implement
		the Cisco Process MIB. This compliance module
		deprecates cProcessMIBCompliance."
	MODULE	-- this module
		MANDATORY-GROUPS { cpmCPUTotalGroupRev, cpmProcessGroupRev}	

	GROUP cpmProcessExtGroupRev
	DESCRIPTION
		"The cpmProcessExtGroupRev is optional for all
		entities. This object is defined after deprecating
		cpmProcessExtGroup."
	
	::= { cpmCompliances 2 }

-- units of conformance

cpmCPUTotalGroup OBJECT-GROUP
	OBJECTS {
		cpmCPUTotalPhysicalIndex
		--cpmCPUTotal5sec,
		--cpmCPUTotal1min,
		--cpmCPUTotal5min,
		--cpmCPUTotal15min
	}
	STATUS  deprecated
	DESCRIPTION
		"A collection of objects providing CPU load monitoring
		information. This group is mandatory for all cisco devices.
		This group is deprecated since the objects cpmCPUTotal5sec,
		cpmCPUTotal1min and cpmCPUTotal5min are
		deprecated. A new object cpmCPUTotalGroupRev is
		added in place of it."
	::= { cpmGroups 1 }

cpmProcessGroup OBJECT-GROUP
	OBJECTS {
		cpmProcessPID,
		cpmProcessName,
		--cpmProcessuSecs,
		cpmProcessTimeCreated
	}
	STATUS	deprecated
	DESCRIPTION
		"A collection of objects providing common process 
		monitoring information. This group is mandatory for 
		all cisco devices. This object is deprecated
		by cpmProcessGroupRev."
	::= { cpmGroups 2 }

--CSCvw30835 Deprecated OIDs needs to be removed from the show snmp mib object-name
--cpmProcessExtGroup OBJECT-GROUP
--	OBJECTS {
		--cpmProcExtMemAllocated,
		--cpmProcExtMemFreed,
		--cpmProcExtInvoked,
		--cpmProcExtRuntime,
		--cpmProcExtUtil5Sec,
		--cpmProcExtUtil1Min,
		--cpmProcExtUtil5Min,
		--cpmProcExtPriority
--	}
--	STATUS	deprecated
--	DESCRIPTION
--		"A collection of objects providing additional and 
--		more detailed process monitoring information. This 
--		group is mandatory for all cisco devices that have 
--		the internal capability to keep this information. 
--		This group is deprecated and new group
--		cpmProcessExtGroupRev is added."
--	::= { cpmGroups 3 }

cpmCPUTotalGroupRev OBJECT-GROUP
	OBJECTS {
		cpmCPUTotalPhysicalIndex,
		--cpmCPUTotal5secRev,
		cpmCPUTotal1minRev,
		cpmCPUTotal5minRev,
		cpmCPUTotal15minRev
	}
	STATUS  current
	DESCRIPTION
		"A collection of objects providing CPU load monitoring
		information. This group is mandatory for all cisco
		devices. This group deprecates cpmCPUTotalGroup."
	::= { cpmGroups 4 }

cpmProcessExtGroupRev OBJECT-GROUP
	OBJECTS {
		cpmProcExtMemAllocatedRev,
		cpmProcExtMemFreedRev,
		cpmProcExtInvokedRev,
		cpmProcExtRuntimeRev,
		cpmProcExtUtil5SecRev,
		cpmProcExtUtil1MinRev,
		cpmProcExtUtil5MinRev,
		cpmProcExtPriorityRev
	}
	STATUS	current
	DESCRIPTION
		"A collection of objects providing additional and 
		more detailed process monitoring information. This 
		group is mandatory for all cisco devices that have 
		the internal capability to keep this information.
		This group is formed after deprecating cpmProcessExtGroup.
		cpmProcExtMemAllocatedRev, cpmProcExtMemFreedRev,
		cpmProcExtInvokedRev, cpmProcExtRuntimeRev,
		cpmProcExtUtil5SecRev, cpmProcExtUtil1MinRev and 
		cpmProcExtUtil5MinRev are the new objects added."
	::= { cpmGroups 5 }

cpmProcessGroupRev OBJECT-GROUP
	OBJECTS {
		cpmProcessPID,
		cpmProcessName,
		cpmProcessAverageUSecs,
		cpmProcessTimeCreated
	}
	STATUS	current
	DESCRIPTION
		"A collection of objects providing common process 
		monitoring information. This group is mandatory for 
		all cisco devices. This object deprecates
		cpmProcessGroup."
	::= { cpmGroups 6 }

END
