-- $Id: CISCO-SYSLOG-MIB.my,v 3.1.46.1 1996/05/21 06:18:16 mordock Exp $
-- $Source: /release/112/cvs/Xsys/MIBS/CISCO-SYSLOG-MIB.my,v $
-- *****************************************************************
-- CISCO-SYSLOG-MIB.my:  Cisco syslog message MIB file
--
-- August 1995, Scott Mordock
--
-- Copyright (c) 1995-1999 by cisco Systems, Inc.
-- All rights reserved.
-- *****************************************************************
-- $Log: CISCO-SYSLOG-MIB.my,v $
--Revision 3.1.46.1  1996/05/21  06:18:16  mordock
--Branch: California_branch
--Improve snmp modularity via creating services to register interfaces
--and chassis cards.
--Add syslog mib.
--
--Revision 3.1  1996/01/19  03:23:55  anke
--Placeholder for Syslog MIB
--
-- *****************************************************************
-- $Endlog$
--

--%DNP%  FYI:  Lines containing a comment starting with the "Do Not
--%DNP%  Publish" prefix "%DNP%" (such as these) are automagicially
--%DNP%  stripped from MIBS prior to publishing on ftp and cio, and
--%DNP%  should be used for comments intended for cisco engineering
--%DNP%  eyes only, or for new product identifiers that are not yet
--%DNP%  announced.

-- This MIB provides a means to gather syslog messages generated
-- by the Cisco IOS

-- Terminology:
-- Various textual messages are generated by the Cisco IOS.  The IOS
-- can be configured such that these messages are sent to a "syslog"
-- server.  With this MIB these same messages can also be received via
-- the SNMP.  These messages are hereupon referred to as "syslog
-- messages" in this document. Note: Messages generated as a result 
-- of entering CLI debug commands are not made available via the SNMP
-- at this time.
-- 
-- All IOS syslog messages have the following attributes:
--	timestamp (optional), facility name (where the message came
--	from), severity, message name, message text
--
-- The following example is often seen:
--	%SYS-5-CONFIG_I: Configured from console ...
-- where facility=SYS, severity=5, message name=CONFIG_I

CISCO-SYSLOG-MIB DEFINITIONS ::= BEGIN

IMPORTS
        MODULE-IDENTITY,
        NOTIFICATION-TYPE,
        OBJECT-TYPE,
	Integer32,
	Counter32
	        FROM SNMPv2-SMI
	TEXTUAL-CONVENTION,
	DisplayString,
	TimeStamp,
	TruthValue
		FROM SNMPv2-TC
        MODULE-COMPLIANCE,
	OBJECT-GROUP
	        FROM SNMPv2-CONF
        ciscoMgmt
	        FROM CISCO-SMI;
     

ciscoSyslogMIB MODULE-IDENTITY
	LAST-UPDATED	"9508070000Z"
	ORGANIZATION	"Cisco Systems, Inc."
	CONTACT-INFO
		"       Cisco Systems
			Customer Service

		Postal: 170 W Tasman Drive
			San Jose, CA  95134
			USA

		   Tel: +1 800 553-NETS

		E-mail: cs-snmp@cisco.com"
	DESCRIPTION
		"The MIB module to describe and store the system messages
		 generated by the IOS."
	::= { ciscoMgmt 41 }

ciscoSyslogMIBObjects OBJECT IDENTIFIER ::= { ciscoSyslogMIB 1 }

-- Subgroups

clogBasic	OBJECT IDENTIFIER ::= { ciscoSyslogMIBObjects 1 }
clogHistory	OBJECT IDENTIFIER ::= { ciscoSyslogMIBObjects 2 }

-- Textual Conventions

SyslogSeverity ::= TEXTUAL-CONVENTION
	STATUS	current
	DESCRIPTION
	       "The severity of a syslog message.  The enumeration
		values are equal to the values that syslog uses + 1.
		For example, with syslog, emergency=0."
	SYNTAX	INTEGER {
			emergency(1),
			alert(2),
			critical(3),
			error(4),
			warning(5),
			notice(6),
			info(7),
			debug(8)
		}

-- Basic syslog objects

clogNotificationsSent OBJECT-TYPE
        SYNTAX          Counter32
	UNITS		"notifications"
        MAX-ACCESS      read-only
        STATUS          current
        DESCRIPTION
	       "The number of clogMessageGenerated notifications that
		have been sent. This number may include notifications 
		that were prevented from being transmitted due to 
		reasons such as resource limitations and/or 
		non-connectivity.  If one is receiving notifications,
		one can periodically poll this object to determine if
		any notifications were missed.  If so, a poll of the
		clogHistoryTable might be appropriate."
	::= { clogBasic 1 }

clogNotificationsEnabled OBJECT-TYPE
        SYNTAX          TruthValue
        MAX-ACCESS      read-write
        STATUS          current
        DESCRIPTION
	       "Indicates whether clogMessageGenerated notifications
		will or will not be sent when a syslog message is
		generated by the device.  Disabling notifications
		does not prevent syslog messages from being added
		to the clogHistoryTable."
	DEFVAL { false }
	::= { clogBasic 2 }

clogMaxSeverity OBJECT-TYPE
        SYNTAX          SyslogSeverity
        MAX-ACCESS      read-write
        STATUS          current
        DESCRIPTION
	       "Indicates which syslog severity levels will be
		processed.  Any syslog message with a severity value
		greater	than this value will be ignored by the agent.
		note: severity numeric values increase as their
		severity decreases, e.g. error(4) is more severe than
		debug(8)."
	DEFVAL { warning }
	::= { clogBasic 3 }

clogMsgIgnores OBJECT-TYPE
        SYNTAX          Counter32
	UNITS		"messages"
        MAX-ACCESS      read-only
        STATUS          current
        DESCRIPTION
	       "The number of syslog messages which were ignored.  A
		message	will be ignored if it has a severity value
		greater	than clogMaxSeverity."
	::= { clogBasic 4 }

clogMsgDrops OBJECT-TYPE
        SYNTAX          Counter32
	UNITS		"messages"
        MAX-ACCESS      read-only
        STATUS          current
        DESCRIPTION
	       "The number of syslog messages which could not be
		processed due to lack of system resources.  Most
		likely this will occur at the same time that syslog
		messages are generated to indicate this lack of
		resources.  Increases in this object's value may serve
		as an indication that system resource levels should be
		examined via other mib objects.  A message that is
		dropped will not appear in the history table and
		no notification will be sent for this message."
	::= { clogBasic 5 }

-- Syslog message history table

clogHistTableMaxLength OBJECT-TYPE
        SYNTAX          Integer32 (0..500)
	UNITS		"entries"
        MAX-ACCESS      read-write
        STATUS          current
        DESCRIPTION
	       "The upper limit on the number of entries that the
		clogHistoryTable may contain.  A value of 0 will
		prevent any history from being retained. When this
		table is full, the oldest entry will be deleted and
		a new one will be created."
        DEFVAL  { 1 }
	::= { clogHistory 1 }

clogHistMsgsFlushed OBJECT-TYPE
        SYNTAX          Counter32
	UNITS		"messages"
        MAX-ACCESS      read-only
        STATUS          current
        DESCRIPTION
	       "The number of entries that have been removed from
		the clogHistoryTable in order to make room for new
		entries.  This object can be utilized to determine
		whether your polling frequency on the history table
		is fast enough and/or the size of your history table
		is large enough such that you are not missing
		messages."
	::= { clogHistory 2 }

clogHistoryTable OBJECT-TYPE
	SYNTAX     SEQUENCE OF ClogHistoryEntry
	MAX-ACCESS not-accessible
	STATUS     current
	DESCRIPTION
	       "A table of syslog messages generated by this device.
		All 'interesting' syslog messages (i.e. severity <=
		clogMaxSeverity) are entered into this table."
	::= { clogHistory 3 }

clogHistoryEntry OBJECT-TYPE
	SYNTAX     ClogHistoryEntry
	MAX-ACCESS not-accessible
	STATUS     current
	DESCRIPTION
	       "A syslog message that was previously generated by this
		device.  Each entry is indexed by a message index."
	INDEX	{ clogHistIndex }
	::= { clogHistoryTable 1 }

ClogHistoryEntry ::=
    SEQUENCE {
	clogHistIndex
		Integer32,
	clogHistFacility
		DisplayString,
	clogHistSeverity
		SyslogSeverity,
	clogHistMsgName
		DisplayString,
	clogHistMsgText
		DisplayString,
	clogHistTimestamp
		TimeStamp
    }

clogHistIndex OBJECT-TYPE
        SYNTAX          Integer32 (1..2147483647)
        MAX-ACCESS      not-accessible
        STATUS          current
        DESCRIPTION
	       "A monotonically increasing integer for the sole
		purpose of indexing messages.  When it reaches the
		maximum value the agent flushes the table and wraps 
		the value back to 1."
	::= { clogHistoryEntry 1 }

clogHistFacility OBJECT-TYPE
        SYNTAX          DisplayString (SIZE (1..20))
        MAX-ACCESS      read-only
        STATUS          current
        DESCRIPTION
	       "Name of the facility that generated this message.
		For example: 'SYS'."
	::= { clogHistoryEntry 2 }

clogHistSeverity OBJECT-TYPE
        SYNTAX          SyslogSeverity
        MAX-ACCESS      read-only
        STATUS          current
        DESCRIPTION
	       "The severity of the message."
	::= { clogHistoryEntry 3 }

clogHistMsgName OBJECT-TYPE
        SYNTAX          DisplayString (SIZE (1..30))
        MAX-ACCESS      read-only
        STATUS          current
        DESCRIPTION
	       "A textual identification for the message type.  A 
		facility name in conjunction with a message name 
		uniquely identifies a message type."
	::= { clogHistoryEntry 4 }

clogHistMsgText  OBJECT-TYPE
	SYNTAX		DisplayString (SIZE (1..255))
	MAX-ACCESS	read-only
	STATUS		current
	DESCRIPTION
               "The text of the message.  If the text of the message
		exceeds 255 bytes, the message will be truncated to
		254 bytes and a '*' character will be appended -
		indicating that the message has been truncated."
	::= { clogHistoryEntry 5 }

clogHistTimestamp  OBJECT-TYPE
	SYNTAX		TimeStamp
	MAX-ACCESS	read-only
	STATUS		current
	DESCRIPTION
               "The value of sysUpTime when this message was generated."
	::= { clogHistoryEntry 6 }


-- notifications

ciscoSyslogMIBNotificationPrefix OBJECT IDENTIFIER ::= { ciscoSyslogMIB 2 }
ciscoSyslogMIBNotifications OBJECT IDENTIFIER 
				::= { ciscoSyslogMIBNotificationPrefix 0 }

clogMessageGenerated NOTIFICATION-TYPE
	OBJECTS	   {	clogHistFacility,
			clogHistSeverity,
			clogHistMsgName,
			clogHistMsgText,
			clogHistTimestamp
		   }
	STATUS	   current
	DESCRIPTION
	       "When a syslog message is generated by the device a
		clogMessageGenerated notification is sent.  The
		sending of these notifications can be enabled/disabled
		via the clogNotificationsEnabled object."
	::= { ciscoSyslogMIBNotifications 1 }

-- conformance information

ciscoSyslogMIBConformance OBJECT IDENTIFIER ::= { ciscoSyslogMIB 3 }
ciscoSyslogMIBCompliances OBJECT IDENTIFIER ::= { ciscoSyslogMIBConformance 1 }
ciscoSyslogMIBGroups	  OBJECT IDENTIFIER ::= { ciscoSyslogMIBConformance 2 }


-- compliance statements

ciscoSyslogMIBCompliance MODULE-COMPLIANCE
      STATUS	current
      DESCRIPTION
		"The compliance statement for entities which implement
		the Cisco syslog MIB."
      MODULE	-- this module
		MANDATORY-GROUPS { ciscoSyslogMIBGroup }
      ::= { ciscoSyslogMIBCompliances 1 }

-- units of conformance

ciscoSyslogMIBGroup OBJECT-GROUP
      OBJECTS {
		clogNotificationsSent,
		clogNotificationsEnabled,
		clogMaxSeverity,
		clogMsgIgnores,
		clogMsgDrops,
		clogHistTableMaxLength,
		clogHistMsgsFlushed,
		clogHistFacility,
		clogHistSeverity,
		clogHistMsgName,
		clogHistMsgText,
		clogHistTimestamp
	}
      STATUS	current
      DESCRIPTION
	"A collection of objects providing the syslog MIB capability."
      ::= { ciscoSyslogMIBGroups 1 }
	
END
